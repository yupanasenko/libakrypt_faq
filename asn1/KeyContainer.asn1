-----------------------------------------------------------------------------------------------
--  Copyright (c) 2014 - 2018 by Axel Kenzo, axelkenzo@mail.ru
-----------------------------------------------------------------------------------------------

KeyContainer DEFINITIONS ::=

BEGIN

-- Секретные данные, помещаемые в контейнер

KeyValue ::= SEQUENCE {
     key       OCTET STRING,
                 -- собственно ключевое значение,
     mask      OCTET STRING,
                 -- маска ключа
     additionalData OCTET STRING OPTIONAL
                 -- дополнительные секретные данные
}

-- Зашифрованныый ключ (зашифрованное DER-представление структуры KeyValue)

EncodedKeyValue ::= OCTET STRING

-- Ресурс ключа симметричного криптографического механизма
-- единица измерения: число использований ключа

CipherKeyResource ::= INTEGER (0 .. 4294967295)

-- Ресурс секретного ключа

KeyResource ::= CHOICE {
     counter      CipherKeyResource
                    -- ресурс ключа симметричного криптографического алгоритма
}

-- Идентификатор криптографического алгоритма

AlgorithmIdentifier  ::=  SEQUENCE  {
     algorithm              OBJECT IDENTIFIER,
                              -- идентификатор алгоритма
     parameters             ANY DEFINED BY algorithm OPTIONAL
}

-- Параметры алгоритмов шифрования и имитозащиты ключа

KeyProtectParameters ::= SEQUENCE {
     iterationCount        INTEGER (0 .. 65535),
                             -- число итераций алгоритма PBKDF2 из Р 50.1.111-2016
     encryptionSalt        OCTET STRING,
                             -- инициализационный вектор для алгоритма PBKDF2
                             -- при генерации ключа шифрования KeyValue
     encryptionMode        AlgorithmIdentifier,
                             -- режим шифрования KeyValue,
                             -- должен содержать идентификатор блочного шифра
                             -- и режим его использования
     encryptionIV          OCTET STRING,
                             -- инициализационный вектор для режима шифрования
     integritySalt         OCTET STRING,
                             -- инициализационный вектор для алгоритма PBKDF2
                             -- при генерации второго ключа - ключа имитозащиты
     hmacIntegrity         OBJECT IDENTIFIER
                             -- идентификатор алгоритма hmac, используемого для 
                             -- контроля целостности секретного ключа
  }

-- Cекретный ключ
SecretKey ::= SEQUENCE {
     value       EncodedKeyValue,
                   -- зашифрованное DER-представление типа KeyValue
     engine      OBJECT IDENTIFIER,
                   -- тип криптографического механизма, для которого предназначен ключ
     number      OCTET STRING,
                   -- номер ключа, по которому может производится его поиск
     parameters  KeyProtectParameters,
                   -- параметры алгоритмов защиты KeyValue
     resource    KeyResource OPTIONAL,
                  -- ресурс ключа
     description UTF8String OPTIONAL
                  -- человекочитаемое описание ключа (в кодировке UTF8)
  }

-- Cекретный ключ, содержащий код целостности
SecretKeyData ::= SEQUENCE {
     data           SecretKey,
                      -- собственно секретный ключ и его данные
     integrityCode  OCTET STRING
                      -- код целостности, вычисляется от DER-представления поля data
                      -- с использованием алгоритма, определенного data.parameters.integrityMode
}

-- ключ, помещаемый в контейнер
AbstractKey ::= CHOICE {
     secretKey  SecretKeyData
                  -- секретный ключ криптографического механизма
}

-- Ключевой контейнер
KeyContainer ::= SEQUENCE {
     version       INTEGER (0..255) DEFAULT 1,
                     -- версия ключевого контейнера
     keys          SEQUENCE OF AbstractKey
                     -- последовательность ключей
}

END
